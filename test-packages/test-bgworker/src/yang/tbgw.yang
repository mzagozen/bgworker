module tbgw {
  yang-version "1.1";
  namespace "http://example.com/tbgw";
  prefix tbgw;

  import tailf-common {
    prefix tailf;
  }

  container tbgw {
    leaf enabled {
      type boolean;
      default true;
    }

    action restart {
      tailf:actionpoint "tbgw-restart";
      output {
        leaf result {
          type string;
        }
      }
    }

    action emergency-stop {
      tailf:actionpoint "tbgw-emergency-stop";
      output {
        leaf result {
          type string;
        }
      }
    }

    leaf counter {
      config false;
      type uint32;
      default 0;
    }
  }

  container tbgw-ha-always {
    leaf enabled {
      type boolean;
      default true;
    }

    leaf counter {
      config false;
      type uint32;
      default 0;
    }
  }

  container tbgw-ha-secondary {
    leaf enabled {
      type boolean;
      default true;
    }

    leaf counter {
      config false;
      type uint32;
      default 0;
    }
  }
}
